# -*- coding: utf-8 -*-
# RIOHS B4 Multimeter Milk Analyzer: Detailed 3D CAD Modeling Macro
# Designed for execution in FreeCAD Python Console or Macro Player.
# Creates the rugged chamfered console shell, vertical display screen pocket, 
# 7-button D-Pad navigation keys, orange side bumpers, and bottom mini-probe pins.

import FreeCAD as App
import Part
import math

# 1. Initialize Document
doc = App.activeDocument()
if doc is None:
    doc = App.newDocument("RIOHS_B4_Multimeter")

print("Generating detailed 3D CAD model for RIOHS B4 Multimeter console...")

# --- Design Dimensions (in mm) ---
CASE_HEIGHT = 135.0
CASE_WIDTH = 68.0
CASE_DEPTH = 24.0

SCREEN_BEZEL_W = 50.0
SCREEN_BEZEL_H = 70.0
SCREEN_BEZEL_D = 2.0

SCREEN_LCD_W = 46.0
SCREEN_LCD_H = 55.0

DPAD_OUTER_R = 22.0
DPAD_DEPTH = 1.5

OK_BTN_R = 7.0
OK_BTN_H = 4.0

DPAD_KEY_W = 12.0
DPAD_KEY_H = 4.0
DPAD_KEY_L = 10.0

AUX_KEY_W = 14.0
AUX_KEY_H = 4.0
AUX_KEY_L = 8.0

BUMPER_W = 4.0
BUMPER_D = 26.0
BUMPER_H = 110.0

PROBE_R = 2.5
PROBE_L = 30.0

# Helper to add shapes to the document and style them
def add_solid(shape, name, color=None):
    obj = doc.addObject("Part::Feature", name)
    obj.Shape = shape
    if color:
        obj.ViewObject.ShapeColor = color
    return obj

# 2. Main Console Casing Body
# Base box
casing_box = Part.makeBox(CASE_WIDTH, CASE_DEPTH, CASE_HEIGHT)
# Center the casing slightly so origin is at the base center (X=0, Y=0)
casing_box.translate(App.Vector(-CASE_WIDTH/2.0, -CASE_DEPTH/2.0, 0.0))

# 3. Cutout for the Screen Bezel
# Placed on the upper half of the front face (Y = CASE_DEPTH/2.0)
screen_pocket = Part.makeBox(SCREEN_BEZEL_W, SCREEN_BEZEL_D + 0.1, SCREEN_BEZEL_H)
screen_pocket.translate(App.Vector(-SCREEN_BEZEL_W/2.0, CASE_DEPTH/2.0 - SCREEN_BEZEL_D, CASE_HEIGHT - SCREEN_BEZEL_H - 12.0))

# Subtract pocket from casing
casing_with_screen = casing_box.cut(screen_pocket)

# 4. Cutout for the D-Pad circular pocket
# Placed on the lower half of the front face
dpad_pocket = Part.makeCylinder(DPAD_OUTER_R, DPAD_DEPTH + 0.1)
# Rotate cylinder so its flat face aligns with the Y axis (front face)
dpad_pocket.rotate(App.Vector(0, 0, 0), App.Vector(1, 0, 0), 90.0)
dpad_pocket.translate(App.Vector(0.0, CASE_DEPTH/2.0 - DPAD_DEPTH, 35.0))

# Subtract D-Pad pocket from casing
casing_final = casing_with_screen.cut(dpad_pocket)

# Add casing to doc (Matte Black / Dark Slate gray)
casing_obj = add_solid(casing_final, "Console_Body", (0.12, 0.12, 0.15))

# 5. Display Screen Panel
screen_lcd = Part.makeBox(SCREEN_LCD_W, 1.0, SCREEN_LCD_H)
screen_lcd.translate(App.Vector(-SCREEN_LCD_W/2.0, CASE_DEPTH/2.0 - SCREEN_BEZEL_D + 0.5, CASE_HEIGHT - SCREEN_BEZEL_H - 8.0))
# Add LCD Screen (Glowing Green style)
screen_obj = add_solid(screen_lcd, "LCD_Display_Screen", (0.2, 0.9, 0.1))

# 6. Buttons
# A. Center OK Button (Orange cylinder)
ok_btn = Part.makeCylinder(OK_BTN_R, OK_BTN_H)
ok_btn.rotate(App.Vector(0, 0, 0), App.Vector(1, 0, 0), 90.0)
ok_btn.translate(App.Vector(0.0, CASE_DEPTH/2.0 - DPAD_DEPTH + OK_BTN_H, 35.0))
ok_btn_obj = add_solid(ok_btn, "OK_Button", (1.0, 0.48, 0.0))

# B. D-Pad Directional Keys (Gray blocks)
# UP Button
up_btn = Part.makeBox(DPAD_KEY_W, DPAD_KEY_H, DPAD_KEY_L)
up_btn.translate(App.Vector(-DPAD_KEY_W/2.0, CASE_DEPTH/2.0 - DPAD_DEPTH, 35.0 + OK_BTN_R + 1.0))
add_solid(up_btn, "DPad_UP_Button", (0.5, 0.5, 0.5))

# DOWN Button
down_btn = Part.makeBox(DPAD_KEY_W, DPAD_KEY_H, DPAD_KEY_L)
down_btn.translate(App.Vector(-DPAD_KEY_W/2.0, CASE_DEPTH/2.0 - DPAD_DEPTH, 35.0 - OK_BTN_R - DPAD_KEY_L - 1.0))
add_solid(down_btn, "DPad_DOWN_Button", (0.5, 0.5, 0.5))

# LEFT Button
left_btn = Part.makeBox(DPAD_KEY_L, DPAD_KEY_H, DPAD_KEY_W)
left_btn.translate(App.Vector(-OK_BTN_R - DPAD_KEY_L - 1.0, CASE_DEPTH/2.0 - DPAD_DEPTH, 35.0 - DPAD_KEY_W/2.0))
add_solid(left_btn, "DPad_LEFT_Button", (0.5, 0.5, 0.5))

# RIGHT Button
right_btn = Part.makeBox(DPAD_KEY_L, DPAD_KEY_H, DPAD_KEY_W)
right_btn.translate(App.Vector(OK_BTN_R + 1.0, CASE_DEPTH/2.0 - DPAD_DEPTH, 35.0 - DPAD_KEY_W/2.0))
add_solid(right_btn, "DPad_RIGHT_Button", (0.5, 0.5, 0.5))

# C. Auxiliary Buttons (Menu, Back)
# MENU Button (Left Aux)
menu_btn = Part.makeBox(AUX_KEY_W, AUX_KEY_H, AUX_KEY_L)
menu_btn.translate(App.Vector(-22.0, CASE_DEPTH/2.0 - DPAD_DEPTH, 12.0))
add_solid(menu_btn, "Menu_Button", (0.35, 0.35, 0.4))

# BACK Button (Right Aux)
back_btn = Part.makeBox(AUX_KEY_W, AUX_KEY_H, AUX_KEY_L)
back_btn.translate(App.Vector(22.0 - AUX_KEY_W, CASE_DEPTH/2.0 - DPAD_DEPTH, 12.0))
add_solid(back_btn, "Back_Button", (0.35, 0.35, 0.4))

# 7. Side Orange Rubber Bumpers
# Left Bumper
left_bumper = Part.makeBox(BUMPER_W, BUMPER_D, BUMPER_H)
left_bumper.translate(App.Vector(-CASE_WIDTH/2.0 - BUMPER_W, -BUMPER_D/2.0, 12.0))
add_solid(left_bumper, "Left_Bumper_Guard", (1.0, 0.48, 0.0))

# Right Bumper
right_bumper = Part.makeBox(BUMPER_W, BUMPER_D, BUMPER_H)
right_bumper.translate(App.Vector(CASE_WIDTH/2.0, -BUMPER_D/2.0, 12.0))
add_solid(right_bumper, "Right_Bumper_Guard", (1.0, 0.48, 0.0))

# 8. Bottom Stainless Steel Mini Probes (coaxial EC and Optical pins)
# Left Probe Pin
left_probe = Part.makeCylinder(PROBE_R, PROBE_L)
left_probe.translate(App.Vector(-12.0, 0.0, -PROBE_L))
left_probe_obj = add_solid(left_probe, "Left_Probe_Pin", (0.8, 0.8, 0.82))

# Right Probe Pin
right_probe = Part.makeCylinder(PROBE_R, PROBE_L)
right_probe.translate(App.Vector(12.0, 0.0, -PROBE_L))
right_probe_obj = add_solid(right_probe, "Right_Probe_Pin", (0.8, 0.8, 0.82))

# 9. Recompute and Redraw Document Tree
doc.recompute()
print("Detailed RIOHS B4 Multimeter 3D CAD model generated successfully!")
