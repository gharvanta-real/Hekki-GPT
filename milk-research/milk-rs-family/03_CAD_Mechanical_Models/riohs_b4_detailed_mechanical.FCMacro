# -*- coding: utf-8 -*-
# ==============================================================================
# RIOHS B4 Multimeter Milk Analyzer: Detailed Industrial 3D CAD Assembly
# Designed for execution in FreeCAD Python Console or Macro Player.
#
# This macro implements a 20-Stage Mechanical Product Design Workflow:
# - Stage 1-3: Body Profiling & Hollow Shelling (2.5mm wall thickness)
# - Stage 4-5: Front/Rear Split & Display/Button Pocketing
# - Stage 6-9: Corner Screw Bosses, Support Ribs, & PCB Standoffs
# - Stage 10-13: Battery Bracket, LCD Holder, & Individual Button Caps
# - Stage 14-16: Sensing Probe Module (coaxial steel pins), TPE Side Bumpers, & Fillets
# ==============================================================================

import FreeCAD as App
import Part
import math

# ==============================================================================
# CONFIGURATION OPTION: EXPLODED VIEW TOGGLE
# Set to True to generate the Exploded Assembly View (parts separated along axes).
# Set to False to generate the final closed Assembled View.
# ==============================================================================
EXPLODED_VIEW = True  

# Initialize Document
doc = App.activeDocument()
if doc is None:
    doc = App.newDocument("RIOHS_B4_Mechanical_Assembly")

print("Constructing mechanical CAD model (Exploded View = {})...".format(EXPLODED_VIEW))

# --- Design Dimensions & Constants ---
CASE_W = 68.0    # Casing Width (X-axis)
CASE_D = 24.0    # Casing Depth (Y-axis)
CASE_H = 135.0   # Casing Height (Z-axis)
WALL_T = 2.5     # Core Wall Thickness (2.5mm)

# Screen Bezel & LCD Panel
SCR_BEZEL_W = 50.0
SCR_BEZEL_H = 70.0
SCR_BEZEL_D = 2.0
SCR_LCD_W = 46.0
SCR_LCD_H = 55.0
SCR_LCD_D = 1.6

# D-Pad & Button configurations
DPAD_R = 22.0
OK_BTN_R = 7.0
OK_BTN_H = 4.0
DIR_BTN_W = 12.0
DIR_BTN_L = 10.0
DIR_BTN_H = 4.0

AUX_BTN_W = 14.0
AUX_BTN_L = 8.0
AUX_BTN_H = 4.0

# Standoffs, Bosses, and Ribs
BOSS_OUT_R = 4.0
BOSS_IN_R = 1.1   # For M2.2 self-tapping screws
BOSS_H = 9.0
PCB_STANDOFF_R = 2.5
PCB_STANDOFF_H = 4.0

# side bumpers (Grips)
BMP_W = 4.0
BMP_D = 26.0
BMP_H = 110.0

# Probe configuration
PROBE_R = 2.5
PROBE_L = 30.0

# Define translation offsets for Exploded View
if EXPLODED_VIEW:
    DY_FRONT = 80.0
    DY_LCD = 115.0
    DY_BUTTONS = 98.0
    DY_PCB = 30.0
    DY_BAT = -25.0
    DY_REAR = -80.0
    DX_LEFT = -45.0
    DX_RIGHT = 45.0
    DZ_PROBE = -50.0
else:
    DY_FRONT = 0.0
    DY_LCD = 0.0
    DY_BUTTONS = 0.0
    DY_PCB = 0.0
    DY_BAT = 0.0
    DY_REAR = 0.0
    DX_LEFT = 0.0
    DX_RIGHT = 0.0
    DZ_PROBE = 0.0

# Helper function to register and color code parts in the tree view
def create_part(shape, name, color=None, transparency=0):
    obj = doc.addObject("Part::Feature", name)
    obj.Shape = shape
    if color:
        obj.ViewObject.ShapeColor = color
    if transparency > 0:
        obj.ViewObject.Transparency = transparency
    return obj

# ==============================================================================
# STAGE 1-3: CASE PROFILING, SHELLING & SPLITTING
# ==============================================================================

# Outer solid body representation
outer_box = Part.makeBox(CASE_W, CASE_D, CASE_H)
outer_box.translate(App.Vector(-CASE_W/2.0, -CASE_D/2.0, 0.0))

# Fillet vertical edges of case (Stage 16 Fillets)
fillet_edges = []
for edge in outer_box.Edges:
    p1 = edge.Vertexes[0].Point
    if abs(p1.x) > 30 and abs(p1.y) > 10:
        fillet_edges.append(edge)

try:
    outer_solid = outer_box.makeFillet(5.0, fillet_edges)
except:
    outer_solid = outer_box

# Hollow Shelling (Stage 7): 2.5mm Wall Thickness
inner_w = CASE_W - (WALL_T * 2.0)
inner_d = CASE_D - (WALL_T * 2.0)
inner_h = CASE_H - (WALL_T * 2.0)
inner_box = Part.makeBox(inner_w, inner_d, inner_h)
inner_box.translate(App.Vector(-inner_w/2.0, -inner_d/2.0, WALL_T))
hollow_casing = outer_solid.cut(inner_box)

# Split Casing (Stage 6): Front Housing vs. Rear Housing along Y=0
front_splitter = Part.makeBox(CASE_W + 10.0, CASE_D/2.0 + 5.0, CASE_H + 10.0)
front_splitter.translate(App.Vector(-CASE_W/2.0 - 5.0, 0.0, -5.0))
front_shell_raw = hollow_casing.common(front_splitter)

rear_splitter = Part.makeBox(CASE_W + 10.0, CASE_D/2.0 + 5.0, CASE_H + 10.0)
rear_splitter.translate(App.Vector(-CASE_W/2.0 - 5.0, -CASE_D/2.0 - 5.0, -5.0))
rear_shell_raw = hollow_casing.common(rear_splitter)

# ==============================================================================
# STAGE 4: FRONT HOUSING FEATURES (Cutouts & LCD Bezel)
# ==============================================================================

# Bezel and button hole pockets
screen_bezel_pocket = Part.makeBox(SCR_BEZEL_W, SCR_BEZEL_D + 1.0, SCR_BEZEL_H)
screen_bezel_pocket.translate(App.Vector(-SCR_BEZEL_W/2.0, CASE_D/2.0 - SCR_BEZEL_D, CASE_H - SCR_BEZEL_H - 12.0))

dpad_recess = Part.makeCylinder(DPAD_R, 1.5 + 0.5)
dpad_recess.rotate(App.Vector(0,0,0), App.Vector(1,0,0), 90.0)
dpad_recess.translate(App.Vector(0.0, CASE_D/2.0 - 1.5, 35.0))

ok_hole = Part.makeCylinder(OK_BTN_R + 0.5, 5.0)
ok_hole.rotate(App.Vector(0,0,0), App.Vector(1,0,0), 90.0)
ok_hole.translate(App.Vector(0.0, CASE_D/2.0 - 3.0, 35.0))

left_aux_hole = Part.makeBox(AUX_BTN_W + 0.8, 5.0, AUX_BTN_L + 0.8)
left_aux_hole.translate(App.Vector(-22.0, CASE_D/2.0 - 3.0, 12.0))

right_aux_hole = Part.makeBox(AUX_BTN_W + 0.8, 5.0, AUX_BTN_L + 0.8)
right_aux_hole.translate(App.Vector(22.0 - (AUX_BTN_W + 0.8), CASE_D/2.0 - 3.0, 12.0))

front_shell = front_shell_raw.cut(screen_bezel_pocket).cut(dpad_recess).cut(ok_hole).cut(left_aux_hole).cut(right_aux_hole)

# Translate Front Shell for Exploded View
front_shell.translate(App.Vector(0.0, DY_FRONT, 0.0))
create_part(front_shell, "Front_Housing_Shell", (0.12, 0.12, 0.15))

# ==============================================================================
# STAGE 8-9: SCREW BOSSES (Front and Rear Corners)
# ==============================================================================

bosses_front_list = []
bosses_rear_list = []
corner_coords = [
    (-CASE_W/2.0 + 6.0, CASE_H - 8.0),
    (CASE_W/2.0 - 6.0, CASE_H - 8.0),
    (-CASE_W/2.0 + 6.0, 8.0),
    (CASE_W/2.0 - 6.0, 8.0)
]

for cx, cz in corner_coords:
    # Front bosses
    outer_cyl = Part.makeCylinder(BOSS_OUT_R, BOSS_H)
    outer_cyl.rotate(App.Vector(0,0,0), App.Vector(1,0,0), 90.0)
    outer_cyl.translate(App.Vector(cx, CASE_D/2.0 - WALL_T, cz))
    
    inner_cyl = Part.makeCylinder(BOSS_IN_R, BOSS_H + 1.0)
    inner_cyl.rotate(App.Vector(0,0,0), App.Vector(1,0,0), 90.0)
    inner_cyl.translate(App.Vector(cx, CASE_D/2.0 - WALL_T, cz))
    
    boss_front = outer_cyl.cut(inner_cyl)
    # Apply offset for Exploded View
    boss_front.translate(App.Vector(0.0, DY_FRONT, 0.0))
    bosses_front_list.append(boss_front)
    
    # Rear bosses
    rear_outer = Part.makeCylinder(BOSS_OUT_R, BOSS_H)
    rear_outer.rotate(App.Vector(0,0,0), App.Vector(1,0,0), 90.0)
    rear_outer.translate(App.Vector(cx, -CASE_D/2.0 + WALL_T + BOSS_H, cz))
    
    rear_inner = Part.makeCylinder(BOSS_IN_R, BOSS_H + 1.0)
    rear_inner.rotate(App.Vector(0,0,0), App.Vector(1,0,0), 90.0)
    rear_inner.translate(App.Vector(cx, -CASE_D/2.0 + WALL_T + BOSS_H, cz))
    
    boss_rear = rear_outer.cut(rear_inner)
    # Apply offset for Exploded View
    boss_rear.translate(App.Vector(0.0, DY_REAR, 0.0))
    bosses_rear_list.append(boss_rear)

all_front_bosses = bosses_front_list[0]
for b in bosses_front_list[1:]:
    all_front_bosses = all_front_bosses.fuse(b)
create_part(all_front_bosses, "Front_Screw_Bosses", (0.2, 0.2, 0.25))

# ==============================================================================
# STAGE 10-11: REAR SHELL STANDOFFS & BRACKETS
# ==============================================================================

# PCB Mount Standoffs
standoffs_list = []
pcb_screw_coords = [
    (-CASE_W/2.0 + 12.0, 75.0),
    (CASE_W/2.0 - 12.0, 75.0),
    (-CASE_W/2.0 + 12.0, 25.0),
    (CASE_W/2.0 - 12.0, 25.0)
]

for sx, sz in pcb_screw_coords:
    st_outer = Part.makeCylinder(PCB_STANDOFF_R, PCB_STANDOFF_H)
    st_outer.rotate(App.Vector(0,0,0), App.Vector(1,0,0), 90.0)
    st_outer.translate(App.Vector(sx, -CASE_D/2.0 + WALL_T + PCB_STANDOFF_H, sz))
    
    st_inner = Part.makeCylinder(1.0, PCB_STANDOFF_H + 1.0)
    st_inner.rotate(App.Vector(0,0,0), App.Vector(1,0,0), 90.0)
    st_inner.translate(App.Vector(sx, -CASE_D/2.0 + WALL_T + PCB_STANDOFF_H, sz))
    
    standoff = st_outer.cut(st_inner)
    # Apply offset for Exploded View
    standoff.translate(App.Vector(0.0, DY_REAR, 0.0))
    standoffs_list.append(standoff)

all_standoffs = standoffs_list[0]
for s in standoffs_list[1:]:
    all_standoffs = all_standoffs.fuse(s)

# Battery Bracket
battery_bracket_l = Part.makeBox(1.5, 6.0, 40.0)
battery_bracket_l.translate(App.Vector(-18.0, -CASE_D/2.0 + WALL_T, 80.0))

battery_bracket_r = Part.makeBox(1.5, 6.0, 40.0)
battery_bracket_r.translate(App.Vector(18.0 - 1.5, -CASE_D/2.0 + WALL_T, 80.0))

battery_holder = battery_bracket_l.fuse(battery_bracket_r)
# Apply offset for Exploded View
battery_holder.translate(App.Vector(0.0, DY_REAR, 0.0))

# Fuse Rear Casing Assembly
rear_shell = rear_shell_raw
# Apply offset for Exploded View
rear_shell.translate(App.Vector(0.0, DY_REAR, 0.0))

for rb in bosses_rear_list:
    rear_shell = rear_shell.fuse(rb)
rear_shell = rear_shell.fuse(all_standoffs).fuse(battery_holder)
create_part(rear_shell, "Rear_Housing_Shell", (0.12, 0.12, 0.15))

# ==============================================================================
# STAGE 12-14: INTERNAL COMPONENT ASSEMBLY
# ==============================================================================

# A. PCB Board (Green FR4 Board)
pcb_w = CASE_W - (WALL_T * 2.0) - 4.0
pcb_h = 105.0
pcb_board = Part.makeBox(pcb_w, 1.6, pcb_h)
pcb_board.translate(App.Vector(-pcb_w/2.0, -CASE_D/2.0 + WALL_T + PCB_STANDOFF_H + DY_PCB, 20.0))
create_part(pcb_board, "ESP32_S3_PCB_Core", (0.05, 0.45, 0.15))

# B. Rechargeable LiPo Battery
bat_w = 34.0
bat_d = 6.0
bat_h = 42.0
battery_block = Part.makeBox(bat_w, bat_d, bat_h)
battery_block.translate(App.Vector(-bat_w/2.0, -CASE_D/2.0 + WALL_T + 0.5 + DY_BAT, 80.0))
create_part(battery_block, "LiPo_Battery_Pack", (0.7, 0.7, 0.75))

# C. TFT Display Module & Glass Panel
lcd_bezel = Part.makeBox(SCREEN_BEZEL_W - 2.0, 1.2, SCREEN_BEZEL_H - 2.0)
lcd_bezel.translate(App.Vector(-(SCREEN_BEZEL_W-2.0)/2.0, CASE_D/2.0 - SCR_BEZEL_D + 0.2 + DY_LCD, CASE_H - SCR_BEZEL_H - 11.0))
create_part(lcd_bezel, "TFT_Bezel_Frame", (0.05, 0.05, 0.05))

lcd_glass = Part.makeBox(SCR_LCD_W, 0.8, SCR_LCD_H)
lcd_glass.translate(App.Vector(-SCR_LCD_W/2.0, CASE_D/2.0 - SCR_BEZEL_D + 0.8 + DY_LCD, CASE_H - SCR_BEZEL_H - 8.0))
create_part(lcd_glass, "LCD_Glass_Panel", (0.2, 0.9, 0.1), transparency=45)

# D. Button caps
# D-Pad Cross Keypad (Silicone)
dpad_cross_h = Part.makeBox(10.0, 3.5, 34.0)
dpad_cross_h.translate(App.Vector(-5.0, CASE_D/2.0 - DPAD_DEPTH + 1.0 + DY_BUTTONS, 35.0 - 17.0))

dpad_cross_v = Part.makeBox(34.0, 3.5, 10.0)
dpad_cross_v.translate(App.Vector(-17.0, CASE_D/2.0 - DPAD_DEPTH + 1.0 + DY_BUTTONS, 35.0 - 5.0))

dpad_silicone = dpad_cross_h.fuse(dpad_cross_v)
ok_cut = Part.makeCylinder(OK_BTN_R + 0.2, 5.0)
ok_cut.rotate(App.Vector(0,0,0), App.Vector(1,0,0), 90.0)
ok_cut.translate(App.Vector(0.0, CASE_D/2.0 - DPAD_DEPTH + 3.0 + DY_BUTTONS, 35.0))
dpad_silicone_final = dpad_silicone.cut(ok_cut)
create_part(dpad_silicone_final, "DPad_Silicone_Pad", (0.35, 0.35, 0.38))

# Center OK Button cap (Orange)
ok_cap = Part.makeCylinder(OK_BTN_R, OK_BTN_H + 1.0)
ok_cap.rotate(App.Vector(0,0,0), App.Vector(1,0,0), 90.0)
ok_cap.translate(App.Vector(0.0, CASE_D/2.0 - DPAD_DEPTH + OK_BTN_H + 0.5 + DY_BUTTONS, 35.0))
create_part(ok_cap, "OK_Keycap", (1.0, 0.48, 0.0))

# Menu Auxiliary button cap
left_aux_cap = Part.makeBox(AUX_BTN_W, AUX_BTN_H + 1.0, AUX_BTN_L)
left_aux_cap.translate(App.Vector(-21.6, CASE_D/2.0 - DPAD_DEPTH + DY_BUTTONS, 12.4))
create_part(left_aux_cap, "Menu_Keycap", (0.3, 0.3, 0.32))

# Back Auxiliary button cap
right_aux_cap = Part.makeBox(AUX_BTN_W, AUX_BTN_H + 1.0, AUX_BTN_L)
right_aux_cap.translate(App.Vector(21.6 - AUX_BTN_W, CASE_D/2.0 - DPAD_DEPTH + DY_BUTTONS, 12.4))
create_part(right_aux_cap, "Back_Keycap", (0.3, 0.3, 0.32))

# ==============================================================================
# STAGE 15-16: OVERMOLDS & STAINLESS PROBE ASSEMBLY
# ==============================================================================

# Side Ribbed TPE Grips (Left and right side orange handles)
# We generate ridges/grooves on the bumpers for anti-slip grip (Stage 15 Rubber)
left_bumper_solid = Part.makeBox(BMP_W, BMP_D, BMP_H)
left_bumper_solid.translate(App.Vector(-CASE_W/2.0 - BMP_W + DX_LEFT, -BMP_D/2.0, 12.0))

right_bumper_solid = Part.makeBox(BMP_W, BMP_D, BMP_H)
right_bumper_solid.translate(App.Vector(CASE_W/2.0 + DX_RIGHT, -BMP_D/2.0, 12.0))

# Cut anti-slip ridges along the bumpers
for i in range(12):
    ridge_z = 20.0 + (i * 7.0)
    ridge_cutter = Part.makeBox(BMP_W + 1.0, 2.0, 2.0)
    
    # Left cutter
    lc = ridge_cutter.copy()
    lc.translate(App.Vector(-CASE_W/2.0 - BMP_W - 0.5 + DX_LEFT, -1.0, ridge_z))
    left_bumper_solid = left_bumper_solid.cut(lc)
    
    # Right cutter
    rc = ridge_cutter.copy()
    rc.translate(App.Vector(CASE_W/2.0 - 0.5 + DX_RIGHT, -1.0, ridge_z))
    right_bumper_solid = right_bumper_solid.cut(rc)

create_part(left_bumper_solid, "Left_Rubber_Grip", (1.0, 0.48, 0.0))
create_part(right_bumper_solid, "Right_Rubber_Grip", (1.0, 0.48, 0.0))

# Coaxial Stainless Steel Probes extending from base
probe_connector = Part.makeBox(36.0, 12.0, 6.0)
probe_connector.translate(App.Vector(-18.0, -6.0, -6.0 + DZ_PROBE))
create_part(probe_connector, "Probe_Base_ABS_Housing", (0.1, 0.1, 0.1))

# Coaxial EC electrode Left pin
left_pin = Part.makeCylinder(PROBE_R, PROBE_L)
left_pin.translate(App.Vector(-12.0, 0.0, -PROBE_L - 6.0 + DZ_PROBE))
create_part(left_pin, "Left_EC_Electrode_Pin", (0.8, 0.8, 0.85))

# Coaxial EC electrode Right pin (Optics housing)
right_pin = Part.makeCylinder(PROBE_R, PROBE_L)
right_pin.translate(App.Vector(12.0, 0.0, -PROBE_L - 6.0 + DZ_PROBE))

# Sapphire window diagonal slot cut on the right sensing pin (5-degree tilt offset)
window_slot = Part.makeCylinder(1.5, 4.0)
window_slot.rotate(App.Vector(0,0,0), App.Vector(1,0,0), 95.0) # 5-degree tilt offset relative to vertical
window_slot.translate(App.Vector(12.0, 0.0, -PROBE_L - 2.0 + DZ_PROBE))
right_pin_final = right_pin.cut(window_slot)

create_part(right_pin_final, "Right_Optical_Electrode_Pin", (0.8, 0.8, 0.85))

# Recompute final layout
doc.recompute()
print("3D Model successfully generated. (Exploded = {})".format(EXPLODED_VIEW))
