# -*- coding: utf-8 -*-
# ==============================================================================
# RIOHS B4 Milk Analyzer: FINAL CONSOLIDATED 3D CAD ASSEMBLY
# Single-file macro that builds the COMPLETE device matching the reference image:
#
#   FRONT:  Hollow shell, LCD bezel, 6 buttons (MENU/BACK/D-PAD/OK/SELECT/POWER)
#   REAR:   Speaker grille, Rating label, Lanyard hole, RIOHS logo
#   BOTTOM: USB-C port
#   RIGHT:  MicroSD slot
#   SIDES:  Orange ribbed TPE bumpers
#   BASE:   Dual SS316 probe pins + ABS connector block
#   INSIDE: PCB, LiPo battery, screw bosses, standoffs
#
# TRL 1-2: Conceptual geometry model. NOT empirically tested in lab.
# ==============================================================================

import FreeCAD as App
import Part
import math
import os

OUTPUT_FILE = "d:/mariano/milk-research/milk-rs-family/cad/riohs_b4_final_assembly.FCStd"

doc = App.activeDocument()
if doc is None:
    doc = App.newDocument("RIOHS_B4_Final_Assembly")
else:
    doc.clearDocument()

print("Building RIOHS B4 Final Assembly...")

# ------------------------------------------------------------------ #
# GLOBAL CONSTANTS (per reference image dimensions)                   #
# ------------------------------------------------------------------ #
CASE_W    = 72.0   # Body width  (mm)
CASE_H    = 175.0  # Body height (mm)
CASE_D    = 35.0   # Body depth  (mm)
WALL_T    = 2.5    # Wall thickness
DRAFT_DEG = 1.5    # Draft angle for injection moulding

# Probe
PIN_R      = 2.5
PIN_L      = 18.0   # 18mm as per reference spec
PIN_SPACE  = 20.0   # 20mm spacing

# Buttons
OK_R    = 7.0
DPAD_R  = 22.0
AUX_W   = 14.0
AUX_H   = 8.0

# Grips
GRIP_W   = 4.5
GRIP_D   = CASE_D + 2.0
GRIP_H   = 130.0

# ------------------------------------------------------------------ #
# HELPER                                                              #
# ------------------------------------------------------------------ #
def add(shape, name, rgb, alpha=0):
    obj = doc.addObject("Part::Feature", name)
    obj.Shape = shape
    if obj.ViewObject is not None:
        obj.ViewObject.ShapeColor = rgb
        if alpha > 0:
            obj.ViewObject.Transparency = alpha
    return obj

# ------------------------------------------------------------------ #
# STAGE 1: OUTER CASING SOLID WITH DRAFT ANGLES                      #
# ------------------------------------------------------------------ #
theta = math.radians(DRAFT_DEG)
t     = CASE_H * math.tan(theta)
W_TOP = CASE_W - 2*t
D_TOP = CASE_D - 2*t

wire_bot = Part.makePolygon([
    App.Vector(-CASE_W/2, -CASE_D/2, 0),
    App.Vector( CASE_W/2, -CASE_D/2, 0),
    App.Vector( CASE_W/2,  CASE_D/2, 0),
    App.Vector(-CASE_W/2,  CASE_D/2, 0),
    App.Vector(-CASE_W/2, -CASE_D/2, 0),
])
wire_top = Part.makePolygon([
    App.Vector(-W_TOP/2, -D_TOP/2, CASE_H),
    App.Vector( W_TOP/2, -D_TOP/2, CASE_H),
    App.Vector( W_TOP/2,  D_TOP/2, CASE_H),
    App.Vector(-W_TOP/2,  D_TOP/2, CASE_H),
    App.Vector(-W_TOP/2, -D_TOP/2, CASE_H),
])
outer_loft = Part.makeLoft([wire_bot, wire_top], True)

# Fillet vertical edges
vert_edges = [e for e in outer_loft.Edges
              if abs(e.Vertexes[0].Point.z - e.Vertexes[1].Point.z) > CASE_H - 5]
try:
    outer_solid = outer_loft.makeFillet(6.0, vert_edges)
except Exception:
    outer_solid = outer_loft

# ------------------------------------------------------------------ #
# STAGE 2: HOLLOW SHELL (2.5 mm WALL)                                #
# ------------------------------------------------------------------ #
WI = CASE_W - 2*WALL_T
DI = CASE_D - 2*WALL_T
HI = CASE_H - WALL_T
inner_box = Part.makeBox(WI, DI, HI)
inner_box.translate(App.Vector(-WI/2, -DI/2, WALL_T))
hollow = outer_solid.cut(inner_box)

# ------------------------------------------------------------------ #
# STAGE 3: SPLIT FRONT / REAR AT Y = 0                               #
# ------------------------------------------------------------------ #
front_cut = Part.makeBox(CASE_W+20, CASE_D/2+10, CASE_H+20)
front_cut.translate(App.Vector(-CASE_W/2-10, 0, -10))
rear_cut  = Part.makeBox(CASE_W+20, CASE_D/2+10, CASE_H+20)
rear_cut.translate(App.Vector(-CASE_W/2-10, -CASE_D/2-10, -10))

front_raw = hollow.common(front_cut)
rear_raw  = hollow.common(rear_cut)

# ------------------------------------------------------------------ #
# STAGE 4: FRONT SHELL FEATURES                                       #
# ------------------------------------------------------------------ #
front = front_raw

# LCD bezel pocket (recessed 2 mm)
lcd_pocket = Part.makeBox(52, WALL_T+1, 72)
lcd_pocket.translate(App.Vector(-26, CASE_D/2 - WALL_T, 88))
front = front.cut(lcd_pocket)

# LCD window through-hole
lcd_window = Part.makeBox(48, 10, 56)
lcd_window.translate(App.Vector(-24, CASE_D/2 - 5, 91))
front = front.cut(lcd_window)

# D-Pad circular recess
dpad_recess = Part.makeCylinder(DPAD_R, 2.5)
dpad_recess.rotate(App.Vector(0,0,0), App.Vector(1,0,0), 90)
dpad_recess.translate(App.Vector(0, CASE_D/2 - 2, 50))
front = front.cut(dpad_recess)

# D-Pad cross slots
slot_v = Part.makeBox(10, 8, 34)
slot_v.translate(App.Vector(-5, CASE_D/2 - 4, 33))
slot_h = Part.makeBox(34, 8, 10)
slot_h.translate(App.Vector(-17, CASE_D/2 - 4, 45))
front = front.cut(slot_v).cut(slot_h)

# OK button hole
ok_hole = Part.makeCylinder(OK_R + 0.5, 8)
ok_hole.rotate(App.Vector(0,0,0), App.Vector(1,0,0), 90)
ok_hole.translate(App.Vector(0, CASE_D/2 - 5, 50))
front = front.cut(ok_hole)

# MENU button slot (upper-left)
menu_slot = Part.makeBox(AUX_W + 1, 8, AUX_H + 1)
menu_slot.translate(App.Vector(-AUX_W/2 - 20, CASE_D/2 - 5, 76))
front = front.cut(menu_slot)

# BACK button slot (upper-right)
back_slot = Part.makeBox(AUX_W + 1, 8, AUX_H + 1)
back_slot.translate(App.Vector(AUX_W/2 + 6, CASE_D/2 - 5, 76))
front = front.cut(back_slot)

# SELECT button slot (lower-left)
sel_slot = Part.makeBox(AUX_W + 1, 8, AUX_H + 1)
sel_slot.translate(App.Vector(-AUX_W/2 - 20, CASE_D/2 - 5, 26))
front = front.cut(sel_slot)

# POWER button slot (lower-right)
pwr_slot = Part.makeBox(AUX_W + 1, 8, AUX_H + 1)
pwr_slot.translate(App.Vector(AUX_W/2 + 6, CASE_D/2 - 5, 26))
front = front.cut(pwr_slot)

front = front.common(outer_solid)
front = front.common(front_cut)
add(front, "Front_Housing_Shell", (0.10, 0.10, 0.12))

# ------------------------------------------------------------------ #
# STAGE 5: REAR SHELL FEATURES                                        #
# ------------------------------------------------------------------ #
rear = rear_raw

# Speaker grille (6 horizontal slots, upper-center rear)
for i in range(6):
    sg = Part.makeBox(20, 2, 2)
    sg.translate(App.Vector(-10, -CASE_D/2 - 0.5, 140 + i*3.5))
    rear = rear.cut(sg)

# Rating label sticker recess
label_recess = Part.makeBox(36, 0.8, 18)
label_recess.translate(App.Vector(-18, -CASE_D/2 + 0.5, 85))
rear = rear.cut(label_recess)

# Lanyard hole (bottom rear)
lanyard = Part.makeCylinder(3, 8)
lanyard.rotate(App.Vector(0,0,0), App.Vector(1,0,0), 90)
lanyard.translate(App.Vector(0, -CASE_D/2 + 8, 8))
rear = rear.cut(lanyard)

# PCB mount standoffs (4 posts)
pcb_posts = [
    (-CASE_W/2 + 12, 75), (CASE_W/2 - 12, 75),
    (-CASE_W/2 + 12, 25), (CASE_W/2 - 12, 25),
]
for px, pz in pcb_posts:
    post_o = Part.makeCylinder(2.5, 4.5)
    post_o.rotate(App.Vector(0,0,0), App.Vector(1,0,0), 90)
    post_o.translate(App.Vector(px, -CASE_D/2 + WALL_T + 4.5, pz))
    post_i = Part.makeCylinder(1.0, 5)
    post_i.rotate(App.Vector(0,0,0), App.Vector(1,0,0), 90)
    post_i.translate(App.Vector(px, -CASE_D/2 + WALL_T + 4.5, pz))
    rear = rear.fuse(post_o.cut(post_i))

# Battery bracket walls
bb_l = Part.makeBox(1.5, 6, 42)
bb_l.translate(App.Vector(-19, -CASE_D/2 + WALL_T, 82))
bb_r = Part.makeBox(1.5, 6, 42)
bb_r.translate(App.Vector(17.5, -CASE_D/2 + WALL_T, 82))
rear = rear.fuse(bb_l).fuse(bb_r)

# Screw bosses (4 corners, rear)
corner_coords = [
    (-CASE_W/2 + 7, CASE_H - 9),
    ( CASE_W/2 - 7, CASE_H - 9),
    (-CASE_W/2 + 7, 9),
    ( CASE_W/2 - 7, 9),
]
for bx, bz in corner_coords:
    bo = Part.makeCylinder(4.0, 9)
    bo.rotate(App.Vector(0,0,0), App.Vector(1,0,0), 90)
    bo.translate(App.Vector(bx, -CASE_D/2 + WALL_T + 9, bz))
    bi = Part.makeCylinder(1.25, 10)
    bi.rotate(App.Vector(0,0,0), App.Vector(1,0,0), 90)
    bi.translate(App.Vector(bx, -CASE_D/2 + WALL_T + 9, bz))
    rear = rear.fuse(bo.cut(bi))

rear = rear.common(outer_solid)
rear = rear.common(rear_cut)
add(rear, "Rear_Housing_Shell", (0.10, 0.10, 0.12))

# ------------------------------------------------------------------ #
# STAGE 6: USB-C PORT (BOTTOM FACE)                                   #
# ------------------------------------------------------------------ #
usb_body = Part.makeBox(9, 3.2, CASE_D + 2)
usb_body.translate(App.Vector(-4.5, -1.6, -1))
usb_tongue = Part.makeBox(7, 1.2, CASE_D - 4)
usb_tongue.translate(App.Vector(-3.5, -0.6, 2))
add(usb_body, "USB_C_Port_Shell", (0.75, 0.75, 0.80))
add(usb_tongue, "USB_C_Internal_Tongue", (0.10, 0.10, 0.10))

# ------------------------------------------------------------------ #
# STAGE 7: MicroSD SLOT (RIGHT FACE)                                  #
# ------------------------------------------------------------------ #
sd_shell = Part.makeBox(5, 15, 2.5)
sd_shell.translate(App.Vector(CASE_W/2 - 0.5, -7.5, 90))
sd_door = Part.makeBox(1, 14, 2)
sd_door.translate(App.Vector(CASE_W/2 + 4.5, -7, 90.25))
add(sd_shell, "MicroSD_Card_Slot", (0.55, 0.55, 0.58))
add(sd_door, "MicroSD_Door_Cover", (0.20, 0.20, 0.22))

# ------------------------------------------------------------------ #
# STAGE 8: BUTTONS                                                    #
# ------------------------------------------------------------------ #
# D-Pad silicone cross pad
dpad_mem = Part.makeCylinder(DPAD_R - 1, 1.0)
dpad_mem.rotate(App.Vector(0,0,0), App.Vector(1,0,0), 90)
dpad_mem.translate(App.Vector(0, CASE_D/2 + 1.5, 50))
cross_v2 = Part.makeBox(10, 3.5, 34)
cross_v2.translate(App.Vector(-5, CASE_D/2 + 0.5, 33))
cross_h2 = Part.makeBox(34, 3.5, 10)
cross_h2.translate(App.Vector(-17, CASE_D/2 + 0.5, 45))
dpad_silicone = dpad_mem.fuse(cross_v2).fuse(cross_h2)
ok_cut2 = Part.makeCylinder(OK_R + 0.3, 5)
ok_cut2.rotate(App.Vector(0,0,0), App.Vector(1,0,0), 90)
ok_cut2.translate(App.Vector(0, CASE_D/2 - 1, 50))
dpad_silicone = dpad_silicone.cut(ok_cut2)
add(dpad_silicone, "DPad_Silicone_Pad", (0.25, 0.25, 0.28))

# OK Keycap (orange)
ok_cap = Part.makeCylinder(OK_R, 4.0)
ok_cap.rotate(App.Vector(0,0,0), App.Vector(1,0,0), 90)
ok_cap.translate(App.Vector(0, CASE_D/2 + 4.5, 50))
ok_flange = Part.makeCylinder(OK_R + 1.2, 1.0)
ok_flange.rotate(App.Vector(0,0,0), App.Vector(1,0,0), 90)
ok_flange.translate(App.Vector(0, CASE_D/2 + 1, 50))
add(ok_cap.fuse(ok_flange), "OK_Keycap", (0.95, 0.40, 0.0))

# MENU Button
menu_btn = Part.makeBox(AUX_W, 3.5, AUX_H)
menu_btn.translate(App.Vector(-AUX_W/2 - 19.5, CASE_D/2 + 0.5, 76.5))
add(menu_btn, "Menu_Button", (0.22, 0.22, 0.25))

# BACK Button
back_btn = Part.makeBox(AUX_W, 3.5, AUX_H)
back_btn.translate(App.Vector(AUX_W/2 + 5.5, CASE_D/2 + 0.5, 76.5))
add(back_btn, "Back_Button", (0.22, 0.22, 0.25))

# SELECT Button (lower-left)
sel_btn = Part.makeBox(AUX_W, 3.5, AUX_H)
sel_btn.translate(App.Vector(-AUX_W/2 - 19.5, CASE_D/2 + 0.5, 26.5))
add(sel_btn, "Select_Button", (0.22, 0.22, 0.25))

# POWER Button (lower-right, red accent)
pwr_btn = Part.makeBox(AUX_W, 3.5, AUX_H)
pwr_btn.translate(App.Vector(AUX_W/2 + 5.5, CASE_D/2 + 0.5, 26.5))
add(pwr_btn, "Power_Button", (0.75, 0.10, 0.10))

# ------------------------------------------------------------------ #
# STAGE 9: ORANGE SIDE GRIPS WITH ANTI-SLIP RIBS                     #
# ------------------------------------------------------------------ #
for side in ['L', 'R']:
    xo = -CASE_W/2 - GRIP_W if side == 'L' else CASE_W/2
    grip = Part.makeBox(GRIP_W, GRIP_D, GRIP_H)
    grip.translate(App.Vector(xo, -GRIP_D/2, 20))
    for i in range(14):
        rz = 25 + i * 7.2
        rc = Part.makeBox(GRIP_W + 1, 2.5, 2.0)
        rc.translate(App.Vector(xo - 0.5, -1.25, rz))
        grip = grip.cut(rc)
    add(grip, "Left_Grip" if side == 'L' else "Right_Grip", (0.95, 0.42, 0.0))

# ------------------------------------------------------------------ #
# STAGE 10: BOTTOM PROBE MODULE                                       #
# ------------------------------------------------------------------ #
probe_base = Part.makeBox(PIN_SPACE + 16, 14, 8)
probe_base.translate(App.Vector(-(PIN_SPACE+16)/2, -7, -8))
add(probe_base, "Probe_ABS_Connector_Block", (0.08, 0.08, 0.08))

# Left EC electrode pin (SS316)
left_pin = Part.makeCylinder(PIN_R, PIN_L)
left_pin.translate(App.Vector(-PIN_SPACE/2, 0, -PIN_L - 8))
add(left_pin, "Left_EC_Electrode_Pin_SS316", (0.82, 0.82, 0.86))

# Right optical electrode pin (SS316, with sapphire window slot)
right_pin = Part.makeCylinder(PIN_R, PIN_L)
right_pin.translate(App.Vector(PIN_SPACE/2, 0, -PIN_L - 8))
sap_slot = Part.makeCylinder(1.4, 4.5)
sap_slot.rotate(App.Vector(0,0,0), App.Vector(1,0,0), 94.0)
sap_slot.translate(App.Vector(PIN_SPACE/2, 0.5, -PIN_L - 3))
add(right_pin.cut(sap_slot), "Right_Optical_Electrode_Pin_SS316", (0.82, 0.82, 0.86))

# ------------------------------------------------------------------ #
# STAGE 11: INTERNAL ELECTRONICS STACK                               #
# ------------------------------------------------------------------ #
pcb_w = CASE_W - 2*WALL_T - 5
pcb = Part.makeBox(pcb_w, 1.6, 108)
pcb.translate(App.Vector(-pcb_w/2, -CASE_D/2 + WALL_T + 5, 18))
add(pcb, "ESP32_S3_PCB_FR4", (0.05, 0.42, 0.12))

shield = Part.makeBox(18, 2.2, 16)
shield.translate(App.Vector(-9, -CASE_D/2 + WALL_T + 5 + 1.6, 72))
add(shield, "ESP32_S3_Shield", (0.78, 0.78, 0.82))

ant = Part.makeBox(12, 1.5, 4)
ant.translate(App.Vector(-6, -CASE_D/2 + WALL_T + 5 + 1.6, 89))
add(ant, "ESP32_Antenna", (0.08, 0.08, 0.10))

ic1 = Part.makeBox(10, 2.0, 10)
ic1.translate(App.Vector(-5, -CASE_D/2 + WALL_T + 5 + 1.6, 55))
add(ic1, "AD5933_IC", (0.12, 0.12, 0.14))

ic2 = Part.makeBox(6, 2.0, 6)
ic2.translate(App.Vector(10, -CASE_D/2 + WALL_T + 5 + 1.6, 58))
add(ic2, "OPA350_IC", (0.12, 0.12, 0.14))

usb_pcb = Part.makeBox(9, 3, 7)
usb_pcb.translate(App.Vector(-4.5, -CASE_D/2 + WALL_T + 5 + 1.6, WALL_T))
add(usb_pcb, "USB_C_PCB_Footprint", (0.72, 0.72, 0.78))

for i in range(4):
    r = Part.makeBox(2, 1.2, 1)
    r.translate(App.Vector(-18 + i*7, -CASE_D/2 + WALL_T + 5 + 1.6, 40 + i*5))
    add(r, "SMD_Resistor_{}".format(i), (0.10, 0.10, 0.10))
    c = Part.makeBox(2.5, 1.5, 2.5)
    c.translate(App.Vector(-18 + i*7, -CASE_D/2 + WALL_T + 5 + 1.6, 30 + i*4))
    add(c, "SMD_Capacitor_{}".format(i), (0.50, 0.42, 0.25))

bat = Part.makeBox(36, 6.5, 45)
bat.translate(App.Vector(-18, -CASE_D/2 + WALL_T + 0.5, 100))
add(bat, "LiPo_Battery_1200mAh", (0.72, 0.72, 0.76))

pcm = Part.makeBox(34, 2.5, 7)
pcm.translate(App.Vector(-17, -CASE_D/2 + WALL_T + 7, 145))
add(pcm, "PCM_Protection_Board", (0.08, 0.08, 0.08))

for col, xo in [((0.85,0.08,0.08), -6), ((0.08,0.08,0.08), 6)]:
    w = Part.makeCylinder(1.0, 12)
    w.rotate(App.Vector(0,0,0), App.Vector(1,0,0), 90)
    w.translate(App.Vector(xo, -CASE_D/2 + WALL_T + 7, 150))
    add(w, "Bat_Wire_{}".format("Red" if xo < 0 else "Blk"), col)

# ------------------------------------------------------------------ #
# STAGE 12: TFT LCD DISPLAY MODULE                                    #
# ------------------------------------------------------------------ #
bezel = Part.makeBox(52, 1.5, 72)
bezel.translate(App.Vector(-26, CASE_D/2 - 1.5, 88))
bezel_win = Part.makeBox(48, 3, 56)
bezel_win.translate(App.Vector(-24, CASE_D/2 - 2, 91))
bezel = bezel.cut(bezel_win)
add(bezel, "TFT_Bezel_Frame", (0.05, 0.05, 0.05))

screen_glass = Part.makeBox(48, 0.8, 56)
screen_glass.translate(App.Vector(-24, CASE_D/2 - 1.0, 91))
add(screen_glass, "LCD_Screen_Glass", (0.18, 0.85, 0.18), alpha=35)

# ------------------------------------------------------------------ #
# STAGE 13: FRONT CORNER SCREW BOSSES                                 #
# ------------------------------------------------------------------ #
for bx, bz in corner_coords:
    bo = Part.makeCylinder(4.0, 9)
    bo.rotate(App.Vector(0,0,0), App.Vector(1,0,0), 90)
    bo.translate(App.Vector(bx, CASE_D/2 - WALL_T, bz))
    bi = Part.makeCylinder(1.1, 10)
    bi.rotate(App.Vector(0,0,0), App.Vector(1,0,0), 90)
    bi.translate(App.Vector(bx, CASE_D/2 - WALL_T, bz))
    boss = bo.cut(bi)
    rib = Part.makeBox(1.5, 9, 1.5)
    rib.translate(App.Vector(bx - 0.75, CASE_D/2 - WALL_T - 9, bz - 0.75))
    nm = "Front_Boss_{}".format("TL" if bx < 0 and bz > 100 else
                                "TR" if bx > 0 and bz > 100 else
                                "BL" if bx < 0 else "BR")
    add(boss.fuse(rib), nm, (0.18, 0.18, 0.22))

# ------------------------------------------------------------------ #
# STAGE 14: M2.2 ASSEMBLY SCREWS                                      #
# ------------------------------------------------------------------ #
screw_names = ["Screw_TL","Screw_TR","Screw_BL","Screw_BR"]
for i, (bx, bz) in enumerate(corner_coords):
    sh = Part.makeCylinder(1.1, 8)
    sh.rotate(App.Vector(0,0,0), App.Vector(1,0,0), 90)
    sh.translate(App.Vector(bx, -CASE_D/2 + 8, bz))
    hd = Part.makeCylinder(2.2, 1.5)
    hd.rotate(App.Vector(0,0,0), App.Vector(1,0,0), 90)
    hd.translate(App.Vector(bx, -CASE_D/2 + 1.5, bz))
    add(sh.fuse(hd), screw_names[i], (0.68, 0.68, 0.72))

# ------------------------------------------------------------------ #
# FINALIZE                                                            #
# ------------------------------------------------------------------ #
doc.recompute()
doc.saveAs(OUTPUT_FILE)
print("Final RIOHS B4 Assembly saved: {} parts total".format(len(doc.Objects)))
print("File: {}".format(OUTPUT_FILE))
